RsaPrivKey ::= SEQUENCE {
	version		INTEGER,
	n		INTEGER ({ rsa_get_n }),
	e		INTEGER ({ rsa_get_e }),
	d		INTEGER ({ rsa_get_d }),
	prime1		INTEGER ({ rsa_get_p }),
	prime2		INTEGER ({ rsa_get_q }),
	exponent1	INTEGER ({ rsa_get_dp }),
	exponent2	INTEGER ({ rsa_get_dq }),
	coefficient	INTEGER ({ rsa_get_qinv })
}
